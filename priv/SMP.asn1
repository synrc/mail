SMP DEFINITIONS IMPLICIT TAGS ::= BEGIN

    -- Auth

    Auth ::= SEQUENCE {
        username INTEGER,
        token OCTET STRING,
        services SET OF value ENUMERATED {
            base      (1),
            groupchat (2),
            messaging (3)
        }
    }

    -- Base Presence

    Person ::= SEQUENCE {
        id INTEGER,
        name OCTET STRING,
        surname OCTET STRING,
        username OCTET STRING,
        status INTEGER
    }

    Presence ::= SEQUENCE {
        size INTEGER,
        userlist SEQUENCE OF Person
    }

    Friend ::= SEQUENCE {
        user Person,
        status INTEGER
    }

    Confirm ::= SEQUENCE {
        user Person,
        type INTEGER
    }

    -- Group Chat

    Room ::= SEQUENCE {
        room INTEGER,
        description INTEGER,
        acl INTEGER,
        settings INTEGER
    }

    Join ::= SEQUENCE {
        user Person,
        room INTEGER,
        answer BOOLEAN
    }

    Public ::= SEQUENCE {
        id INTEGER,
        room INTEGER,
        message OCTET STRING,
        author Person
    }

    -- Messaging

    Private ::= SEQUENCE {
        id OCTET STRING,
        author Person,
        body OCTET STRING,
        status INTEGER
    }

    Typing ::= SEQUENCE {
        room INTEGER,
        author Person
    }

    -- API

    Retrieve ::= SEQUENCE {
        id OCTET STRING,
        chat OCTET STRING
    }

    Mark ::= SEQUENCE {
        id OCTET STRING,
        room OCTET STRING,
        status INTEGER -- DELETE, ARCHIVE, FAVOURITE, SHARED
    }

    Search ::= SEQUENCE {
        id OCTET STRING,
        body OCTET STRING,
        author OCTET STRING
    }

END
